HUMAN-CARE-MIB DEFINITIONS ::= BEGIN

IMPORTS
	enterprises, Gauge
		FROM RFC1155-SMI
	OBJECT-TYPE
		FROM RFC-1212
    XYZCorp	
		FROM XYZCorp-MIB;

-- Initial MIB specification for a manageable body area network system. The focus is to build a monitoring system for high-risk environments, enabling a central manager to monitor user's health state and take corresponding according to the information provided by agents installed on users' uniforms. The information capture is handled by a number of sensors which work in synergy with the agents. AUTHORS: Amanda Rieth Torbes, Paulo Renato Lanzarin.

humanCare            OBJECT IDENTIFIER ::= { XYZCorp 6 }

-- General information regarding a monitored user.

hcUserInfo           OBJECT IDENTIFIER ::= { humanCare 1 }

-- Sensor information regarding the monitored user's body and health state.

hcBody               OBJECT IDENTIFIER ::= { humanCare 2 }

-- Information about the environment in which the monitored user's current on.

hcEnvironment        OBJECT IDENTIFIER ::= { humanCare 3 }

-- General information about sensors connected to the user's agent.

hcSensor             OBJECT IDENTIFIER ::= { humanCare 4 }

-- Data about the network connecting the user's agent to any kind of manager (in progress).

hcNetwork            OBJECT IDENTIFIER ::= { humanCare 5 }

usrName  OBJECT-TYPE
	SYNTAX     OCTET STRING
	ACCESS     read-write
	STATUS     mandatory
	DESCRIPTION 
		"Name of the currently monitored user."
	::= { hcUserInfo 1 }

usrAge  OBJECT-TYPE
	SYNTAX     INTEGER
	ACCESS     read-write
	STATUS     mandatory
	DESCRIPTION 
		"Age of the currently monitored user."
	::= { hcUserInfo 2 }

usrGender  OBJECT-TYPE
	SYNTAX     OCTET STRING
	ACCESS     read-write
	STATUS     mandatory
	DESCRIPTION 
		"Gender of the currently monitored user."
	::= { hcUserInfo 3 }

usrLatitude  OBJECT-TYPE
	SYNTAX     INTEGER
	ACCESS     read-only
	STATUS     optional
	DESCRIPTION 
		"Location: current latitude coordinate of the monitored user."
	::= { hcUserInfo 4 }

usrLongitude  OBJECT-TYPE
	SYNTAX     INTEGER
	ACCESS     read-only
	STATUS     optional
	DESCRIPTION 
		"Location: current longitude coordinate of the monitored user."
	::= { hcUserInfo 5 }

usrOrientationX  OBJECT-TYPE
	SYNTAX     INTEGER
	ACCESS     read-only
	STATUS     optional
	DESCRIPTION 
		"Accelerometer data: x axis of monitored user's orientation."
	::= { hcUserInfo 6 }

usrOrientationY  OBJECT-TYPE
	SYNTAX     INTEGER
	ACCESS     read-only
	STATUS     optional
	DESCRIPTION 
		"Accelerometer data: y axis of monitored user's orientation."
	::= { hcUserInfo 7 }

usrOrientationZ  OBJECT-TYPE
	SYNTAX     INTEGER
	ACCESS     read-only
	STATUS     optional
	DESCRIPTION 
		"Accelerometer data: z axis of monitored user's orientation."
	::= { hcUserInfo 8 }



bdBloodPressure  OBJECT-TYPE
	SYNTAX     Gauge
	ACCESS     read-only
	STATUS     optional
	DESCRIPTION 
		"Mean arterial pressure of the monitored user, measured in mmHg (milimeter of mercury)."
	::= { hcBody 1 }

bdTemperature  OBJECT-TYPE
	SYNTAX     INTEGER
	ACCESS     read-only
	STATUS     optional
	DESCRIPTION 
		"User's body temperature measured in degree celsius."
	::= { hcBody 2 }

bdHeartRate  OBJECT-TYPE
	SYNTAX     Gauge
	ACCESS     read-only
	STATUS     optional
	DESCRIPTION 
		"User's heartbeat rate measured in beats per minute (bpm)."
	::= { hcBody 3 }

bdHeartRhythmLeadI  OBJECT-TYPE
	SYNTAX     Gauge
	ACCESS     read-only
	STATUS     optional
	DESCRIPTION 
		"Heart rhythm: lead I signal emitted by user's sensor to measure heart rhythm."
	::= { hcBody 4 }

bdHeartRhythmLeadII  OBJECT-TYPE
	SYNTAX     Gauge
	ACCESS     read-only
	STATUS     optional
	DESCRIPTION 
		"Heart rhythm: lead II signal emitted by user's sensor to measure heart rhythm."
	::= { hcBody 5 }

bdBloodGlucose  OBJECT-TYPE
	SYNTAX     Gauge
	ACCESS     read-only
	STATUS     optional
	DESCRIPTION 
		"User's mean glucose level, or blood sugar, measured in mg/dL (milligrams per decilitre)."
	::= { hcBody 6 }

bdBloodOxygenSaturation  OBJECT-TYPE
	SYNTAX     Gauge
	ACCESS     read-only
	STATUS     optional
	DESCRIPTION 
		"User's oxygen saturation level, given by the percentage of oxygen being transported by the user's blood."
	::= { hcBody 7 }

envHumidity  OBJECT-TYPE
	SYNTAX     Gauge
	ACCESS     read-only
	STATUS     optional
	DESCRIPTION 
		"Current environment's humidity level (percentage of water vapor in the air)."
	::= { hcEnvironment 1 }

envTemperature  OBJECT-TYPE
	SYNTAX     INTEGER
	ACCESS     read-only
	STATUS     optional
	DESCRIPTION 
		"Current environment's temperature measured in degree celsius."
	::= { hcEnvironment 2 }

envLuminosity  OBJECT-TYPE
	SYNTAX     Gauge
	ACCESS     read-only
	STATUS     optional
	DESCRIPTION 
		"Current environment's luminosity level measured in candela."
	::= { hcEnvironment 3 }

envOxygen  OBJECT-TYPE
	SYNTAX     Gauge
	ACCESS     read-only
	STATUS     optional
	DESCRIPTION 
		"Current environment's oxygen level (percentage of oxygen in the air)."
	::= { hcEnvironment 4 }

envAlarm  OBJECT-TYPE
	SYNTAX     INTEGER
	ACCESS     read-write
	STATUS     mandatory
	DESCRIPTION 
		"An object used to determine if the environment's alarm should be activated. Its behaviour is that of a boolean variable (1 - activate, 0 - off)."
	::= { hcEnvironment 5 }

hcSensorNumber  OBJECT-TYPE
	SYNTAX     Gauge
	ACCESS     read-only
	STATUS     mandatory
	DESCRIPTION 
		"Number of sensors being used in this monitoring session."
	::= { hcSensor 1 }

hcSensorTable  OBJECT-TYPE
	SYNTAX SEQUENCE OF HcSensorEntry
	ACCESS     not-accessible
	STATUS     mandatory
	DESCRIPTION 
		""
	::= { hcSensor 2 }


hcSensorEntry  OBJECT-TYPE
	SYNTAX 	HcSensorEntry
	ACCESS     not-accessible
	STATUS     mandatory
	DESCRIPTION 
		""
	INDEX { sensorType }
	::= { hcSensorTable 1 }

HcSensorEntry ::= SEQUENCE {
    sensorIndex
        INTEGER,
	sensorType
		INTEGER,
	sensorLocation
		OCTET STRING,
	sensorBatteryPower
		Gauge,
	sensorBatteryAlert
		INTEGER
}

sensorIndex OBJECT-TYPE
	SYNTAX     INTEGER
	ACCESS     read-only
	STATUS     mandatory
	DESCRIPTION 
		"Sensor index."
	::= { hcSensorEntry 1 }

sensorType  OBJECT-TYPE
	SYNTAX     INTEGER
	ACCESS     read-only
	STATUS     mandatory
	DESCRIPTION 
		"Sensor's identification number which determines its type in accordance to an enumerated table."
	::= { hcSensorEntry 2 }

sensorLocation  OBJECT-TYPE
	SYNTAX     OCTET STRING
	ACCESS     read-write
	STATUS     mandatory
	DESCRIPTION 
		"Textual description of the sector and/or location the sensor is current on and responsible for."
	::= { hcSensorEntry 3 }

sensorBatteryPower  OBJECT-TYPE
	SYNTAX     Gauge
	ACCESS     read-only
	STATUS     mandatory
	DESCRIPTION 
		"Sensor's battery level (0-100)."
	::= { hcSensorEntry 4 }

sensorBatteryAlert  OBJECT-TYPE
	SYNTAX     INTEGER
	ACCESS     read-write
	STATUS     mandatory
	DESCRIPTION 
		"Sensor's battery alert indicator (1 - alert. 0 - normal). Should be used to enable visual feedback about the sensor's recharging need."
	::= { hcSensorEntry 5 }

END

-- This MIB was created using NuDesign Technologies' Visual MIBuilder (Ver 5.2).
